-- ALCATEL RFC1155-SMI MIB
-- ===========================================================================
-- This MIB module is implemented in Alcatel's ASAM 7301 System Rel 5.0
-- The following definition was extracted from rfc1155
-- and modified to reflect Alcatel's implementation.
-- These modifications are required to get the MIB module to be
-- compiled by:
--   * a reference MIB compiler: SMICNG version 2.2.07;
--   * the Alcatel proprietary MIB compiler: MIBCO
--   Note that this is not completely transparent because MIBCO does not support
--   the "SMI" construct used in this MIB.
--
         -- CONTACT-INFO "Marc Van Vlimmeren"
         -- Postal: Alcatel Bell Telephone
         -- Francis Wellesplein 1
         -- 2018 Antwerpen
         -- BELGIUM

-- ===========================================================================
--  HISTORY:
--
--  date: 2001-11-27  -  version: 3EC36726AAAA_E5.0.0.0
--  editor: Marc Van Vlimmeren
--  Modifications are required to allow the MIB module to be
--  compiled by:
--     * a reference MIB compiler: SMICNG version 2.2.07;
--     * the Alcatel proprietary MIB compiler: MIBCO
--     Note that this is not completely transparent because MIBCO does not support
--     the "SMI" construct used in this MIB.
--  Major changes with respect to standard version:
--     * Removed EXPORTS.
--     * Added explicit definitions of ccitt, null, iso, org, and dod.
--     * Commented out OBJECT-TYPE macro definition (since will use
--        the definition from RFC1212).
--     * added SMIC directives for enable definition of syntax types, to allow
--       compilation with SMICNG. By default, SMIC directives are commented out
--       and normal syntax types are used. This allows compilation by MIBCO.
--       When compiling with SMICNG, the normal syntax types shall be
--       commented out and SMIC directives shall be enabled.
--
--  date: 2002-06-17  -  version: 3EC36726AAAA_E5.0.0.1
--  editor: Marc Van Vlimmeren
--  Changes: commented out definitions of ccitt and iso because they are
--           not correct according to the object identifier syntax. Also
--           commented out the definition of null because it cannot be parsed
--           by the browsertool, used within the engineering department.

-- ===========================================================================


RFC1155-SMI DEFINITIONS ::= BEGIN

	IMPORTS	OBJECT-TYPE FROM RFC-1212;

--            EXPORTS -**- EVERYTHING
--                    internet, directory, mgmt,
--                    experimental, private, enterprises,
--                    OBJECT-TYPE, ObjectName, ObjectSyntax, SimpleSyntax,
--                    ApplicationSyntax, NetworkAddress, IpAddress,
--                    Counter, Gauge, TimeTicks, Opaque;

        -- Define OIDs
        ccitt        OBJECT IDENTIFIER ::= { 0 }
        null         OBJECT IDENTIFIER ::= { ccitt 0 }

        iso          OBJECT IDENTIFIER ::= { 1 }
        org          OBJECT IDENTIFIER ::= { iso 3 }
        dod          OBJECT IDENTIFIER ::= { org 6 }
        internet     OBJECT IDENTIFIER ::= { dod 1 }
        directory    OBJECT IDENTIFIER ::= { internet 1 }
        mgmt         OBJECT IDENTIFIER ::= { internet 2 }
        experimental OBJECT IDENTIFIER ::= { internet 3 }
        private      OBJECT IDENTIFIER ::= { internet 4 }
        enterprises  OBJECT IDENTIFIER ::= { private 1 }

        snmpV2         OBJECT IDENTIFIER ::= { internet 6 }
        snmpDomains    OBJECT IDENTIFIER ::= { snmpV2 1 }
        snmpModules    OBJECT IDENTIFIER ::= { snmpV2 3 }
        snmpMIB OBJECT IDENTIFIER ::=  { snmpModules 1 }

        snmpMIBObjects OBJECT IDENTIFIER ::=  { snmpMIB 1 }

        snmpTrap       OBJECT IDENTIFIER ::= { snmpMIBObjects 4 }
        snmpTraps      OBJECT IDENTIFIER ::=  { snmpMIBObjects 5 }	

        snmpTrapOID OBJECT-TYPE
          SYNTAX     OBJECT IDENTIFIER
          ACCESS     not-accessible
          STATUS     mandatory
          DESCRIPTION
                  "The authoritative identification of the trap
                  currently being sent.  This variable occurs as the
                  second varbind of a SNMPv2-Trap-PDU."
          ::= { snmpTrap 1 }

        snmpTrapEnterprise OBJECT-TYPE
          SYNTAX OBJECT IDENTIFIER
          ACCESS read-only
          STATUS mandatory
          DESCRIPTION
                  "The authoritative identification of the enterprise
                  associated with the trap currently being sent.  When a
                  SNMPv2 proxy agent is mapping an RFC1157 Trap-PDU into a
                  SNMPv2-Trap-PDU, this variable occurs as the last varbind."
          ::=  { snmpTrap 3 }

        snmpColdStartTrap OBJECT-TYPE
          SYNTAX     OBJECT IDENTIFIER
          ACCESS     not-accessible
          STATUS     mandatory
          DESCRIPTION
                  "Reference to the cold-start trap"
          ::= { snmpTraps 1 }

        snmpWarmStartTrap OBJECT-TYPE
          SYNTAX     OBJECT IDENTIFIER
          ACCESS     not-accessible
          STATUS     mandatory
          DESCRIPTION
                  "Reference to the warm-start trap"
          ::= { snmpTraps 2 }

        snmpLinkDownTrap OBJECT-TYPE
          SYNTAX     OBJECT IDENTIFIER
          ACCESS     not-accessible
          STATUS     mandatory
          DESCRIPTION
                  "Reference to the link-down trap"
          ::= { snmpTraps 3 }

        snmpLinkUpTrap OBJECT-TYPE
          SYNTAX     OBJECT IDENTIFIER
          ACCESS     not-accessible
          STATUS     mandatory
          DESCRIPTION
                  "Reference to the link-up trap"
          ::= { snmpTraps 4 }

        snmpAuthenticationFailureTrap OBJECT-TYPE
          SYNTAX     OBJECT IDENTIFIER
          ACCESS     not-accessible
          STATUS     mandatory
          DESCRIPTION
                  "Reference to the authentication failure trap"
          ::= { snmpTraps 5 }

        snmpEqpNeighbourLossTrap OBJECT-TYPE
          SYNTAX     OBJECT IDENTIFIER
          ACCESS     not-accessible
          STATUS     mandatory
          DESCRIPTION
                  "Reference to the eqp-neighbour-loss trap"
          ::= { snmpTraps 6 }

        -- Make builtin items known
        -- SMI NetworkAddress
        -- SMI IpAddress
        -- SMI Counter
        -- SMI Gauge
        -- SMI TimeTicks
        -- SMI Opaque


        -- definition of object types

--     ALCATEL NOTE:  OBJECT-TYPE macro definition commented out since
--     the definition from RFC1212 shall be used.

        --    OBJECT-TYPE MACRO ::=
        --    BEGIN
        --        TYPE NOTATION ::= "SYNTAX" type (TYPE ObjectSyntax)
        --                          "ACCESS" Access
        --                          "STATUS" Status
        --        VALUE NOTATION ::= value (VALUE ObjectName)
        --
        --        Access ::= "read-only"
        --                        | "read-write"
        --                        | "write-only"
        --                        | "not-accessible"
        --        Status ::= "mandatory"
        --                        | "optional"
        --                        | "obsolete"
        --    END
        --
        -- names of objects in the MIB

               ObjectName ::= OBJECT IDENTIFIER

        -- syntax of objects in the MIB

               ObjectSyntax ::=
                   CHOICE {
                       simple
                           SimpleSyntax,
               -- note that simple SEQUENCEs are not directly
               -- mentioned here to keep things simple (i.e.,
               -- prevent mis-use).  However, application-wide
               -- types which are IMPLICITly encoded simple
               -- SEQUENCEs may appear in the following CHOICE

                       application-wide
                           ApplicationSyntax
                   }

                  SimpleSyntax ::=
                      CHOICE {
                          number INTEGER,
                          string OCTET STRING,
                          object OBJECT IDENTIFIER,
                          empty  NULL
                      }

                  ApplicationSyntax ::=
                      CHOICE {
                          address NetworkAddress,
                          counter Counter,
                          gauge Gauge,
                          ticks TimeTicks,
                          arbitrary Opaque
                  -- other application-wide types, as they are
                  -- defined, will be added here
                      }


                  -- application-wide types

                  NetworkAddress ::=
                      CHOICE {
                          internet IpAddress
                      }

                  IpAddress ::=
                      [APPLICATION 0]
                          IMPLICIT OCTET STRING (SIZE (4))

                  Counter ::=
                      [APPLICATION 1]
                          IMPLICIT INTEGER (0..4294967295)

                  Gauge ::=
                      [APPLICATION 2]
                          IMPLICIT INTEGER (0..4294967295)

                  TimeTicks ::=
                      [APPLICATION 3]
                          IMPLICIT INTEGER (0..4294967295)

                  Opaque ::=
                      [APPLICATION 4]
                          IMPLICIT OCTET STRING
END
